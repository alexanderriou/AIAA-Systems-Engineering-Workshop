package Harrier_Requirements {
    doc /* This is the requirements of the whole harrier system. */

    requirement def test_req {
        doc /* This is a test requirement to toy around with the SysIDE functionality. */
    }

}
